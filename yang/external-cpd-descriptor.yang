module external-cpd-descriptor {
  namespace "urn:etsi:mec:external-cpd-descriptor";
  prefix ecpd;

  import ietf-inet-types {
    prefix inet;
  }
  import ietf-yang-types {
    prefix yang;
  }
  import common { prefix comm; }

  description "Data model for ETSI MEC Application External CPD";

  grouping external-cpd-descriptor {
    description "Describes an external connection point of a MEC application";

    list virtual-network-interface-requirements {
      key id;
      description "Specifies requirements on a virtual network interface realizing the CPs instantiated from this CPD.";
      uses virtual-network-interface-requirements;
    }

    uses cpd;
  }

  grouping virtual-network-interface-requirements {
    description "Specifies requirements on a virtual network interface";
    reference "ETSI GS NFV-IFA 011: Network Functions Virtualisation (NFV) Release 3;
               Management and Orchestration;
               VNF Descriptor and Packaging Specification, clause 7.1.6.6";

    leaf id {
      type string;
      description "Identifier of the virtual network interface requirement";
    }

    leaf name {
      type string;
      description "Provides a human readable name for the requirement.";
    }
    leaf description {
      type string;
      description "Provides a human readable description of the requirement.";
    }
    leaf support-mandatory {
      type boolean;
      default true;
      description "Indicates whether fulfilling the constraint is mandatory (true) for successful operation.";
    }
    list network-interface-requirements {
      description "";
      key "key";
      uses comm:key-value-pair;
    }
    list niclo-requirements {
      description "This references (couples) the CPD with any logical node I/O requirements (for network devices) that may have been created. Linking these attributes is necessary so that I/O requirements that need to be articulated at the logical node level can be associated with the network interface requirements associated with the CPD.";
      key "id";
      uses logical-node-requirements;
    }
  }

  grouping logical-node-requirements {
    leaf id {
      type string;
      description "Identifier of the logical node requirement";
    }
    list logical-node-requirement-details {
      description "The logical node-level compute, memory and I/O requirements. An array of key-value pairs that articulate the deployment requirements. This could include the number of CPU cores on this logical node, a memory configuration specific to a logical node (e.g. such as available in the Linux kernel via the libnuma library) or a requirement related to the association of an I/O device with the logical node.";
      key "key";
      uses comm:key-value-pair;
    }
  }

  typedef layer-protocol-type {
    type enumeration {
      enum ETHERNET { value 0; }
      enum MPLS { value 1; }
      enum ODU2 { value 2; }
      enum IPV4 { value 3; }
      enum IPV6 { value 4; }
      enum PSEUDO_WIRE { value 5; }
    }
  }

  grouping cpd {
    description "Describes a Connection Point";
    reference "ETSI GS NFV-IFA 011: Network Functions Virtualisation (NFV) Release 3;
               Management and Orchestration;
               VNF Descriptor and Packaging Specification, clause 7.1.6.3";

    leaf id {
      type string;
      description "Identifier of this Cpd information element.";
    }
    leaf k8s-cluster-net {
      type string;
      description "K8s cluster network";
    }
    leaf-list layer-protocol {
      type layer-protocol-type;
      description "Identifies which protocol the CP uses for connectivity purposes.";
    }
    leaf cp-role {
      type string;
      description "Identifies the role of the CP in the context of the traffic flow patterns in the VNF or parent NS.";
    }
    leaf description {
      type string;
      description "Provides human-readable information on the purpose of the CP.";
    }
    leaf trunk-mode {
      type boolean;
      description "Specifies whether the CP is a trunk port (true) or not (false).";
    }
    leaf-list security-group-rule-id {
      type string;
      description "Identifies the security group rules bound to the CP.";
    }
    list cp-protocol {
      key "associated-layer-protocol";
      leaf associated-layer-protocol {
        type layer-protocol-type;
        description "Identifies the layer protocol associated with the CP.";
      }
      list address-data {
        key "id";
        description "Provides information on the addresses to be assigned to the CP(s) instantiated from this CPD.";

        leaf id {
          type string;
          description "Identifier of this address data information element.";
        }

        leaf address-type {
          type enumeration {
            enum MAC_ADDRESS;
            enum IP_ADDRESS;
          }
          description "Describes the type of the address to be assigned to the CP instantiated from this CPD.";
        }

        leaf l2-address-data {
          when "../address-type = 'MAC_ADDRESS'";
          type yang:mac-address;
          description "Specifies the L2 address to be assigned to the CP instantiated from this CPD.";
        }

        container l3-address-data {
          when "../address-type = 'IP_ADDRESS'";
          description "The L3 address data for the CP instantiated from this CPD.";

          leaf ip-address-type {
            type enumeration {
              enum IPV4;
              enum IPV6;
            }
            description "The type of the IP address.";
          }

          leaf number-of-ip-addresses {
            type uint32;
            description "The number of IP addresses to assign to the CP instantiated from this CPD.";
          }

          leaf-list ip-address-assignment {
            type enumeration {
              enum DYNAMIC;
              enum STATIC;
            }
            description "Specifies how the IP address(es) will be assigned.";
          }

          leaf-list floating-ip-activated {
            type boolean;
            description "Specify if the floating IP scheme is activated on the CP instantiated from this CPD.";
          }

          leaf-list fixed-ip-address {
            type inet:ip-address;
            description "Specifies the fixed IP address(es) to assign to the CP instantiated from this CPD.";
          }
        }
      }
    }
  }
}
