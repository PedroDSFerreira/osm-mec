module change-app-instance-state-op-config-descriptor {
  namespace "http://example.com/ns/change-app-instance-state-op-config";
  prefix caisoc;

  description "YANG module for Change Application Instance State Operation Configuration.";

  grouping change-app-instance-state-op-config-descriptor {
    description "Parameters for the change application instance state operation.";

    leaf min-graceful-stop-timeout {
      type uint32;
      mandatory true;
      description "Minimum timeout value for graceful stop of a VNF instance.";
    }

    leaf max-recommended-graceful-stop-timeout {
      type uint32;
      description "Maximum recommended timeout value that can be needed to gracefully stop a VNF instance of a particular type under certain conditions, such as maximum load condition.";
    }

    list vnf-parameters {
      key "key";
      description "Array of KVP requirements for VNF-specific parameters to be passed when invoking the OperateVnf operation.";

      leaf key {
        type string;
        description "Key of the VNF-specific parameter.";
      }

      leaf value {
        type string;
        description "Value of the VNF-specific parameter.";
      }
    }
  }
}
