module terminate-app-instance-op-config-descriptor {
  namespace "http://example.com/ns/terminate-app-instance-op-config";
  prefix taio;

  description "YANG module for Terminate Application Instance Operation Configuration.";

  grouping terminate-app-instance-op-config-descriptor {
    description "Parameters for the terminate application instance operation.";

    leaf min-graceful-termination-timeout {
      type uint32;
      mandatory true;
      description "Minimum timeout value for graceful termination of a VNF instance.";
    }

    leaf max-recommended-graceful-termination-timeout {
      type uint32;
      description "Maximum recommended timeout value that can be needed to gracefully terminate a VNF instance of a particular type under certain conditions, such as maximum load condition.";
    }

    list vnf-parameters {
      key "key";
      description "Array of KVP requirements for VNF-specific parameters to be passed when invoking the OperateVnf operation.";

      leaf key {
        type string;
        description "Key of the VNF-specific parameter.";
      }

      leaf value {
        type string;
        description "Value of the VNF-specific parameter.";
      }
    }
  }
}
