module service-descriptor {
  namespace "urn:etsi:mec:service-descriptor";
  prefix sd;

  import ietf-inet-types {
    prefix inet;
  }

  organization "ETSI MEC ISG";
  description "Data model for ETSI MEC Service Descriptor";

  revision 2024-03-12 {
    description "Initial revision";
  }

  container categories {
    description "Service categories";
    list category {
      key id;
      uses CategoryRef;
    }
  }

  grouping CategoryRef {
    description "A Category reference";
    
    leaf href {
      type string;
      description "Reference of the catalogue";
    }
    
    leaf id {
      type string;
      description "Unique identifier of the category";
    }
    
    leaf name {
      type string;
      description "Name of the category";
    }
    
    leaf version {
      type string;
      description "Category version";
    }
  }

  grouping TransportDescriptor {
    description "Describes a transport";
    
    leaf id {
      type string;
      mandatory true;
      description "The identifier of this transport";
    }
    
    leaf name {
      type string;
      mandatory true;
      description "The name of this transport";
    }
    
    leaf description {
      type string;
      description "Human-readable description of this transport";
    }
    
    leaf type {
      type enumeration {
        enum REST_HTTP;
        enum MB_TOPIC_BASED;
        enum MB_ROUTING;
        enum MB_PUBSUB;
        enum RPC;
        enum RPC_STREAMING;
        enum WEBSOCKET;
      }
      mandatory true;
      description "Type of the transport";
    }
    
    leaf protocol {
      type string;
      mandatory true;
      description "The name of the protocol used";
    }
    
    leaf version {
      type string;
      mandatory true;
      description "The version of the protocol used";
    }
    
    container endpoint {
      description "Information about the endpoint to access the transport";
      uses EndPointInfo;
    }
    
    container security {
      description "Information about the security used by the transport";
      uses SecurityInfo;
    }
    
    container implSpecificInfo {
      description "Additional implementation specific details of the transport";
    }
  }

  grouping EndPointInfo {
    description "Information about a transport endpoint";
    
    leaf-list uris {
      type inet:uri;
      description "Entry point information of the service as URI";
    }
    
    list addresses {
      key "host";
      description "Entry point information as IP address and port";
      
      leaf host {
        type inet:host;
        description "IP address of the entry point";
      }
      
      leaf port {
        type inet:port-number;
        description "Port of the entry point";
      }
    }
  }

  grouping SecurityInfo {
    description "Information about the security used by a transport";
    
    container oAuth2Info {
      description "Information about OAuth2 based security";
      
      leaf-list grantTypes {
        type enumeration {
          enum OAUTH2_AUTHORIZATION_CODE;
          enum OAUTH2_IMPLICIT_GRANT;
          enum OAUTH2_RESOURCE_OWNER;
          enum OAUTH2_CLIENT_CREDENTIALS;
        }
        min-elements 1;
        max-elements 4;
        description "Supported OAuth2 grant types";
      }
      
      leaf tokenEndpoint {
        when "not(../grantTypes[.='OAUTH2_IMPLICIT_GRANT'])";
        type inet:uri;
        mandatory true;
        description "The token endpoint";
      }
    }
  }

  typedef SerializerType {
    type enumeration {
      enum JSON {
        description "JavaScript Object Notation as defined in RFC 8259";
      }
      enum XML {
        description "Extensible Markup Language as defined in W3C REC-xml-20081126";
      }
      enum PROTOBUF3 {
        description "Protocol Buffers version 3 as defined in https://developers.google.com/protocol-buffers/docs/reference/proto3-spec";
      }
    }
    description "Types of serializers";
  }

  grouping ServiceDescriptor {
    description "Describes a service";
    
    leaf serName {
      type string;
      mandatory true;
      description "The name of the service, e.g. RNIS, LocationService";
    }
    
    container serCategory {
      description "A Category reference of the service";
      uses CategoryRef;
    }
    
    leaf version {
      type string;
      mandatory true;
      description "The version of the service";
    }
    
    list transportsSupported {
      key "transportId";
      min-elements 1;
      description "Transports and serializers supported by the service";
      
      leaf transportId {
        type string;
        description "Unique identifier for the transport binding";
      }
      
      container transport {
        description "Information about the transport";
        uses TransportDescriptor;
      }
      
      leaf-list serializers {
        type SerializerType;
        min-elements 1;
        description "Serializers supported for this transport binding";
      }
    }
  }
}
