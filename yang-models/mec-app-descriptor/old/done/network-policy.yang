module app-network-policy {
  namespace "http://example.com/ns/app-network-policy";
  prefix anp;

  description "YANG module for Application Network Policy.";

  grouping app-network-policy {
    description "Grouping for application network policy.";

    container app-network-policy {
      description "This attribute provides an option for the application to specify a type of network to carry the application traffic.";

      leaf cellularNetwork {
        type boolean;
        default false;
        description "If present, and the application prefers to a cellular network to carry its traffic, this attribute shall be set to true. Otherwise, it shall be set to false.";
      }

      leaf wi-fiNetwork {
        type boolean;
        default false;
        description "If present, and the application prefers to a Wi-Fi network to carry its traffic, this attribute shall be set to true. Otherwise, it shall be set to false.";
      }

      leaf fixedAccessNetwork {
        type boolean;
        default false;
        description "If present, and the application prefers to a fixed access network to carry its traffic, this attribute shall be set to true. Otherwise, it shall be set to false.";
      }
    }
  }
}
