module service-dependency {
  namespace "urn:etsi:mec:service-dependency";
  prefix srvd;

  description "Data model for ETSI MEC Service Dependency";

  grouping CategoryRef {
    description "A Category reference";

    leaf href {
      type string;
      mandatory true;
      description "Reference of the catalogue";
    }

    leaf id {
      type string;
      mandatory true;
      description "Unique identifier of the category";
    }

    leaf name {
      type string;
      mandatory true;
      description "Name of the category";
    }

    leaf version {
      type string;
      mandatory true;
      description "Category version";
    }
  }

  grouping TransportDependency {
    description "Describes transport dependencies of a MEC app";

    leaf transport {
      type string;
      mandatory true;
      description "Information about the transport in this transport binding";
    }

    leaf-list serializers {
      type string;
      min-elements 1;
      description "Information about the serializers in this transport binding";
    }

    leaf-list labels {
      type string;
      min-elements 1;
      description "Set of labels that allow to define groups of transport bindings";
    }
  }

  grouping ServiceDependency {
    description "Describes service dependencies of a MEC app";

    leaf serName {
      type string;
      mandatory true;
      description "The name of the service, e.g. RNIS, LocationService, AMS";
    }

    container serCategory {
      description "A Category reference of the service";
      uses CategoryRef;
    }

    leaf version {
      type string;
      mandatory true;
      description "The version of the service";
    }

    list serTransportDependencies {
      key "transportId";
      description "Indicates transport and serialization format dependencies of consuming the service. Defaults to REST + JSON if absent.";

      leaf transportId {
        type string;
        description "Unique identifier for the transport dependency";
      }

      uses TransportDependency;
    }

    leaf-list requestedPermissions {
      type string;
      description "Requested permissions regarding the access of the application to the service. The format is left for the data model design stage.";
      reference "ETSI GS MEC 009 clause 7.2";
    }
  }
}
