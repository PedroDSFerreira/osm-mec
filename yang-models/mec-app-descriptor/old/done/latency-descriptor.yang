module latency-descriptor {
  namespace "http://example.com/ns/latency-descriptor";
  prefix ld;

  description "YANG module for Latency Descriptor.";

  grouping latency-descriptor-grouping {
    description "Grouping for Latency Descriptor.";

    container latency-descriptor {
      description "Container for latency descriptor attributes.";

      leaf maxLatency {
        type uint32;
        units "ns";
        mandatory true;
        description "The value of the maximum latency in nano seconds tolerated by the MEC application.";
      }
    }
  }
}
