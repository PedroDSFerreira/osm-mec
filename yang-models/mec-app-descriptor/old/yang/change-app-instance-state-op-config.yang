module change-app-instance-state-op-config {
  namespace "http://example.com/ns/change-app-instance-state-op-config";
  prefix caisoc;

  description "YANG module for Change Application Instance State Operation Configuration.";

  grouping change-app-instance-state-op-config-grouping {
    description "Grouping for Change Application Instance State Operation Configuration.";

    container change-app-instance-state-op-config {
      description "Configuration parameters for the change application instance state operation.";

      leaf minGracefulStopTimeout {
        type uint32;
        mandatory true;
        description "Minimum timeout value for graceful stop of a VNF instance.";
      }

      leaf maxRecommendedGracefulStopTimeout {
        type uint32;
        description "Maximum recommended timeout value that can be needed to gracefully stop a VNF instance of a particular type under certain conditions, such as maximum load condition.";
      }

      list parameter {
        key "key";
        description "Array of KVP requirements for VNF-specific parameters to be passed when invoking the OperateVnf operation.";

        leaf key {
          type string;
          description "Key of the VNF-specific parameter.";
        }

        leaf value {
          type string;
          description "Value of the VNF-specific parameter.";
        }
      }
    }
  }
}
