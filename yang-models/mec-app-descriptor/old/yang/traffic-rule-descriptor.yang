module traffic-rule-descriptor {
  namespace "urn:etsi:mec:traffic-rule-descriptor";
  prefix trd;

  import ietf-inet-types {
    prefix inet;
  }
  import ietf-yang-types {
    prefix yang;
  }

  organization "ETSI MEC ISG";
  description "Data model for ETSI MEC Traffic Rule Descriptor";

  revision 2024-03-11 {
    description "Initial revision";
  }

  typedef Identifier {
    type string;
    description "An identifier, e.g. a UUID";
  }

  grouping TrafficFilter {
    description "The filter used to identify specific flow/packets";
    
    leaf-list srcAddress {
      type inet:ip-address;
      description "An IP address or a range of IP addresses";
    }
    
    leaf-list dstAddress {
      type inet:ip-address;  
      description "An IP address or a range of IP addresses";
    }
    
    leaf-list srcPort {
      type inet:port-number;
      description "A port or a range of ports";  
    }
    
    leaf-list dstPort {
      type inet:port-number;
      description "A port or a range of ports";
    }
    
    leaf-list protocol {
      type uint8;
      description "Specify the protocol of the traffic filter";
    }
    
    leaf-list tag {
      type string;
      description "Used for tag based traffic rule";
    }
    
    leaf-list uri {
      type string;
      description "An URI label used to filter the traffic";
    }
    
    leaf-list packetLabel {
      type string;
      description "A customized packet label used to filter traffic";
    }
    
    leaf-list srcTunnelAddress {
      type inet:ip-address;
      description "Used for GTP tunnel based traffic rule";
    }
    
    leaf-list tgtTunnelAddress {
      type inet:ip-address;
      description "Used for GTP tunnel based traffic rule";  
    }
    
    leaf-list srcTunnelPort {
      type inet:port-number;
      description "Used for GTP tunnel based traffic rule";
    }
    
    leaf-list dstTunnelPort {
      type inet:port-number;
      description "Used for GTP tunnel based traffic rule";
    }
    
    leaf qCI {
      type uint8;
      description "Used to match all packets that have the same QCI";
    }
    
    leaf dSCP {
      type uint8;
      description "Used to match all IPv4 packets with same DSCP";
    }
    
    leaf tC {
      type uint8;  
      description "Used to match all IPv6 packets with same TC";
    }
  }

  grouping InterfaceDescriptor {
    description "Describes an interface of a MEC application";
    
    leaf interfaceType {
      type enumeration {
        enum TUNNEL;
        enum MAC;
        enum IP;
      }
      mandatory true;
      description "Type of interface: TUNNEL, MAC, IP, etc";
    }
    
    container tunnelInfo {
      when "../interfaceType = 'TUNNEL'";
      description "Included only if interfaceType is TUNNEL";
      uses TunnelInfo;
    }
    
    leaf srcMACAddress {
      when "../interfaceType = 'MAC'";
      type yang:mac-address;
      description "Source MAC address if interfaceType is MAC";
    }
    
    leaf dstMACAddress {
      when "../interfaceType = 'MAC'";
      type yang:mac-address;
      description "Destination MAC address if interfaceType is MAC";
    }
    
    leaf dstIPAddress {
      when "../interfaceType = 'IP'";
      type inet:ip-address;
      description "Destination IP address if interfaceType is IP";
    }
  }

  grouping TunnelInfo {
    description "Parameters for traffic rules using tunnels";
    
    leaf tunnelType {
      type enumeration {
        enum GTP-U;
        enum GRE;
      }
      mandatory true;
      description "Type of tunnel: GTP-U, GRE, etc";
    }
    
    leaf tunnelDstAddress {
      type inet:ip-address;
      mandatory true;
      description "Destination address of the tunnel";
    }
    
    leaf tunnelSrcAddress {
      type inet:ip-address;
      mandatory true;
      description "Source address of the tunnel";  
    }
    
    container tunnelSpecificData {
      description "Parameters specific to the tunnel type";
    }
  }

  grouping TrafficRuleDescriptor {
    description "Describes traffic rules related to a MEC app";
    
    list trafficRule {
      key "trafficRuleId";
      
      leaf trafficRuleId {
        type Identifier;
        description "Identifies the traffic rule";
      }
      
      leaf filterType {
        type enumeration {
          enum FLOW;
          enum PACKET;
        }
        mandatory true;
        description "Filter type: per FLOW or PACKET";
      }
      
      leaf priority {
        type uint8;
        mandatory true;
        description "Priority of traffic rule from 0 to 255";
      }
      
      list trafficFilter {
        key "filterId";
        min-elements 1;
        description "Filter to identify specific flow/packets";
        
        leaf filterId {
          type string;
          description "Unique identifier for the traffic filter";
        }
        
        uses TrafficFilter;  
      }
      
      leaf action {
        type enumeration {
          enum DROP;
          enum FORWARD_DECAPSULATED;
          enum FORWARD_AS_IS; 
          enum PASSTHROUGH;
          enum DUPLICATED_DECAPSULATED;
          enum DUPLICATE_AS_IS;
        }
        mandatory true;
        description "Action when packet matches trafficFilter";
      }
      
      list dstInterface {
        key "interfaceId";
        max-elements 2;
        description "Destination interface if action is FORWARD";
        
        leaf interfaceId {
          type string;
          description "Unique identifier for the interface";
        }
        
        uses InterfaceDescriptor;
      }
    }
  }
}
