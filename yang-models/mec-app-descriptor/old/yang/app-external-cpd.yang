module app-external-cpd {
  namespace "urn:etsi:mec:app-external-cpd";
  prefix aecpd;

  import ietf-inet-types {
    prefix inet;
  }
  import ietf-yang-types {
    prefix yang;
  }

  organization "ETSI MEC ISG";
  description "Data model for ETSI MEC Application External CPD";

  revision 2024-03-14 {
    description "Initial revision";
  }

  grouping VirtualNetworkInterfaceRequirements {
    description "Specifies requirements on a virtual network interface";
    reference "ETSI GS NFV-IFA 011: Network Functions Virtualisation (NFV) Release 3;
               Management and Orchestration;
               VNF Descriptor and Packaging Specification, clause 7.1.6.6";

    leaf name {
      type string;
      description "Provides a human readable name for the requirement.";
    }
    leaf description {
      type string;
      description "Provides a human readable description of the requirement.";
    }
    leaf supportMandatory {
      type boolean;
      default true;
      description "Indicates whether fulfilling the constraint is mandatory (true) for successful operation.";
    }
    leaf requirement {
      type string;
      description "Specifies a requirement such as the support of SR-IOV, a particular data plane acceleration library, an API, or a hardware capability.";
    }
  }

  grouping Cpd {
    description "Describes a Connection Point";
    reference "ETSI GS NFV-IFA 011: Network Functions Virtualisation (NFV) Release 3;
               Management and Orchestration;
               VNF Descriptor and Packaging Specification, clause 7.1.6.3";

    leaf cpdId {
      type string;
      description "Identifier of this Cpd information element.";
    }
    leaf layerProtocol {
      type enumeration {
        enum ETHERNET;
        enum MPLS;
        enum ODU2;
        enum IPV4;
        enum IPV6;
        enum PSEUDO_WIRE;
      }
      description "Identifies which protocol the CP uses for connectivity purposes.";
    }
    leaf cpRole {
      type string;
      description "Identifies the role of the CP in the context of the traffic flow patterns in the VNF or parent NS.";
    }
    leaf description {
      type string;
      description "Provides human-readable information on the purpose of the CP.";
    }
    list addressData {
      key "addressType";
      description "Provides information on the addresses to be assigned to the CP(s) instantiated from this CPD.";
      
      leaf addressType {
        type enumeration {
          enum MAC_ADDRESS;
          enum IP_ADDRESS;
        }
        description "Describes the type of the address to be assigned to the CP instantiated from this CPD.";
      }
      
      leaf l2AddressData {
        when "../addressType = 'MAC_ADDRESS'";
        type yang:mac-address;
        description "Specifies the L2 address to be assigned to the CP instantiated from this CPD.";
      }
      
      container l3AddressData {
        when "../addressType = 'IP_ADDRESS'";
        description "The L3 address data for the CP instantiated from this CPD.";
        
        leaf ipAddressType {
          type enumeration {
            enum IPV4;
            enum IPV6;
          }
          description "The type of the IP address.";
        }
        
        leaf numberOfIpAddress {
          type uint32;
          description "The number of IP addresses to assign to the CP instantiated from this CPD.";
        }
        
        leaf-list ipAddressAssignment {
          type enumeration {
            enum DYNAMIC;
            enum STATIC;
          }
          description "Specifies how the IP address(es) will be assigned.";
        }
        
        leaf-list floatingIpActivated {
          type boolean;
          description "Specify if the floating IP scheme is activated on the CP instantiated from this CPD.";
        }
        
        leaf-list ipAddressReservation {
          type inet:ip-address;
          description "Specifies the IP addresses to be assigned.";
        }
      }
    }
  }

  grouping AppExternalCpd {
    description "Describes an external connection point of a MEC application";
    
    list virtualNetworkInterfaceRequirements {
      key name;
      description "Specifies requirements on a virtual network interface realizing the CPs instantiated from this CPD.";
      uses VirtualNetworkInterfaceRequirements;
    }
    
    uses Cpd;
  }
}
