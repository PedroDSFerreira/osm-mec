module mec-app-descriptor {
  namespace "http://example.com/ns/mec-app-descriptor";
  prefix mad;

  import external-cpd-descriptor { prefix ecpd; }
  import terminate-app-instance-op-config-descriptor { prefix taio; }
  import transport-dependency-descriptor {prefix td; }
  import traffic-rule-descriptor { prefix trd; }
  import change-app-instance-state-op-config-descriptor { prefix caisoc; }
  import user-context-transfer-capability-descriptor { prefix uctc; }
  import network-policy-descriptor { prefix np; }
  import dns-rule-descriptor { prefix dr; }
  import latency-descriptor { prefix l; }
  import sw-image-descriptor { prefix si; }
  import virtual-storage-descriptor { prefix vs; }
  import feature-dependency-descriptor { prefix fd; }
  import service-dependency-descriptor { prefix srv; }
  import service-descriptor { prefix sd; }

  description "YANG module for MEC Application Descriptors based on ETSI GS MEC 010-2 V2.2.1.";

  container app-descriptor {
    leaf id {
      type string;
      description "Identifier of this MEC application descriptor. This attribute shall be globally unique.";
    }
    leaf name {
      type string;
      description "Name to identify the MEC application.";
    }
    leaf provider {
      type string;
      description "Provider of the application and of the AppD.";
    }
    leaf soft-version {
      type string;
      description "Identifies the version of software of the MEC application.";
    }
    leaf version {
      type string;
      description "Identifies the version of the application descriptor.";
    }
    leaf mec-version {
      type string;
      description "Identifies version(s) of MEC system compatible with the MEC application described in this version of the AppD. The value shall be formatted as comma-separated list of strings.";
    }
    leaf info-name {
      type string;
      description "Human readable name for the MEC application.";
    }
    leaf description {
      type string;
      description "Human readable description of the MEC application.";
    }
    container network-policy {
      description "Application network policy.";
      uses np:network-policy-descriptor;
    }
    container sw-image {
      description "Incorporates the Software Image Descriptor into the MEC application descriptor.";
      uses si:sw-image-descriptor;
    }
    list dns-rule {
      description "Incorporates the DNS Rule Descriptor into the MEC application descriptor.";
      key "id";
      uses dr:dns-rule-descriptor;
    }
    container latency {
      description "Incorporates the Latency Descriptor into the MEC application descriptor.";
      uses l:latency-descriptor;
    }
    list virtual-storage {
      description "Incorporates Virtual Storage Descriptor into the MEC application descriptor.";
      key "id";
      uses vs:virtual-storage-descriptor;
    }
    container user-context-transfer-capability {
      description "Incorporates the user context transfer capability attributes into the MEC application descriptor.";
      uses uctc:user-context-transfer-capability-descriptor;
    }
    container feature-dependency {
      description "Incorporates the Feature Dependency into the MEC application descriptor.";
      uses fd:feature-dependency-descriptor;
    }
    container change-app-instance-state-op-config {
      description "Incorporates the Change Application Instance State Operation Configuration into the MEC application descriptor.";
      uses caisoc:change-app-instance-state-op-config-descriptor;
    }
    container terminate-app-instance-op-config {
      description "Incorporates the Terminate Application Instance Operation Configuration into the MEC application descriptor.";
      uses taio:terminate-app-instance-op-config-descriptor;
    }
    list traffic-rule {
      description "Incorporates the Traffic Rule Descriptor into the MEC application descriptor.";
      key "id";
      uses trd:traffic-rule-descriptor;
    }
    list transport-dependency {
      key "id";
      min-elements 1;
      description
          "List of transport dependencies";
      uses td:transport-dependency-descriptor;
    }
    list ext-cpd{
      key id;
      description "Describes an external connection point of a MEC application";
      uses ecpd:external-cpd-descriptor;
    }
    list service-required {
      description "Describes service dependencies of the MEC app";
      key "name";
      uses srv:service-dependency-descriptor;
    }
    list service-produced {
      description "Describes services a MEC application is able to produce to the platform or other MEC applications. Only relevant for service producing apps.";
      key "name";
      uses sd:service-descriptor;
    }
  }
}
