module sw-image-descriptor {
  namespace "http://example.com/ns/sw-image-descriptor";
  prefix sid;

  description "YANG module for Software Image Descriptor.";

  grouping sw-image-descriptor {
    description "Software Image Descriptor.";

    leaf id {
      type string;
      mandatory true;
      description "The identifier of this software image.";
    }

    leaf name {
      type string;
      mandatory true;
      description "The name of this software image.";
    }

    leaf version {
      type string;
      mandatory true;
      description "The version of this software image.";
    }

    leaf checksum {
      type string;
      mandatory true;
      description "The checksum of the software image file.";
    }

    leaf container-format {
      type string;
      mandatory true;
      description "The container format describes the container file format in which software image is provided.";
    }

    leaf disk-format {
      type string;
      description "The disk format of a software image is the format of the underlying disk image.";
    }

    leaf min-disk {
      type uint64;
      description "The minimal disk size requirement for this software image.";
    }

    leaf min-ram {
      type uint64;
      description "The minimal RAM requirement for this software image.";
    }

    leaf size {
      type uint64;
      mandatory true;
      description "The size of this software image file.";
    }

    leaf sw-image {
      type string;
      mandatory true;
      description "This is a reference to the actual software image.";
    }

    leaf operating-system {
      type string;
      description "Specifies the operating system used in the software image.";
    }

    leaf-list supported-virtualisation-environment {
      type string;
      description "Specifies the virtualisation environments compatible with this software image.";
    }
  }
}
